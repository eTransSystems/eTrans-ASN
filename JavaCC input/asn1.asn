JacExample DEFINITIONS IMPLICIT TAGS ::=

BEGIN

-- In below example the class "AvailabilityStatus.java" will be generated by JAC, 
-- but the inner elements of SequenceOf record will not be defined in the created class. 
-- You should focus the inner elements manually.

AvailabilityStatus ::= SEQUENCE OF INTEGER 
{ inTest(0), failed(1), powerOff(2), offLine(3) }



-- In the below asn1 definition, JAC will not create TaggedtypeExample.java class by default, because here it is defined as a "tagged type".
-- But you can still generate your java class by JAC.
-- It is very simple to generate java classes of tagged types with a little modification inside your asn.1 file.
-- Have a look at the comments in the top of the generated  "examples\TaggedTypeExample.java" class  in the project to understand how to do.

TaggedTypeExample   ::= [20] EXPLICIT   INTEGER

END
